(defun c:test1 ( / e i n s x )
(setq str1 "===========")
(print str1)
    (if (setq s (ssget))
        (progn
            (setq i 0
                  n (sslength s)
            )
            (while (< i n)
                (setq e (ssname s i)
                      x (command "_list" entl (entget e))
                      i (1+ i)
                )
                (print x)
            )
        )
    )
    (princ)
)

(defun C:L2P ( / ss)
;;; Line 2 Polyline
(setq ss (ssget "_I"))
(while (not ss)(setq ss (ssget)))
(if (and (getvar "PEDITACCEPT") (= (getvar "PEDITACCEPT") 1))
(vl-cmdf "_pedit" "_Multiple" ss "" "")
(vl-cmdf "_pedit" "_Multiple" ss "" "_Y" "")
)
)
